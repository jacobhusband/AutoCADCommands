(vl-load-com)

(defun S::STARTUP ()
  (command "NETLOAD" "C:\\Users\\jakeh\\source\\repos\\AutoCADCommands\\AutoCADCommands\\bin\\Debug\\AutoCADCommands.dll")
  (princ "GMEPElectricalCommands.dll loaded.")
)

(princ)
